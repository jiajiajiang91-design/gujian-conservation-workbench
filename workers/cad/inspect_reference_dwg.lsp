(vl-load-com)

(defun gj-clean (value / text)
  (setq text (if value (vl-princ-to-string value) ""))
  (setq text (vl-string-translate "\t\r\n" "   " text))
  text
)

(defun gj-write (stream fields / first field)
  (setq first T)
  (foreach field fields
    (if first
      (setq first nil)
      (write-char 9 stream)
    )
    (princ (gj-clean field) stream)
  )
  (princ "\n" stream)
)

(defun gj-inc (key values / existing)
  (setq existing (assoc key values))
  (if existing
    (subst (cons key (1+ (cdr existing))) existing values)
    (cons (cons key 1) values)
  )
)

(defun gj-safe-get (object property / value)
  (setq value (vl-catch-all-apply 'vlax-get-property (list object property)))
  (if (vl-catch-all-error-p value) "" value)
)

(defun c:GJINSPECT (/ output stream selection index entity data entityType layer layoutName typeCounts layerCounts layoutCounts insertCounts textValue textCount layerRecord blockRecord)
  (setq output (getenv "GUJIAN_DWG_REPORT"))
  (if (not output)
    (progn (princ "GUJIAN_DWG_REPORT is not set") (exit))
  )
  (setq stream (open output "w"))
  (gj-write stream (list "DRAWING" (getvar "DWGNAME") (getvar "DWGPREFIX")))
  (gj-write stream (list "VERSION" (getvar "ACADVER")))
  (gj-write stream (list "INSUNITS" (getvar "INSUNITS")))
  (gj-write stream (list "MEASUREMENT" (getvar "MEASUREMENT")))
  (gj-write stream (list "EXTMIN" (getvar "EXTMIN")))
  (gj-write stream (list "EXTMAX" (getvar "EXTMAX")))

  (setq selection (ssget "_X"))
  (setq index 0 typeCounts nil layerCounts nil layoutCounts nil insertCounts nil textCount 0)
  (if selection
    (repeat (sslength selection)
      (setq entity (ssname selection index))
      (setq data (entget entity))
      (setq entityType (cdr (assoc 0 data)))
      (setq layer (cdr (assoc 8 data)))
      (setq layoutName (cdr (assoc 410 data)))
      (setq typeCounts (gj-inc entityType typeCounts))
      (setq layerCounts (gj-inc layer layerCounts))
      (setq layoutCounts (gj-inc (if layoutName layoutName "") layoutCounts))
      (if (= entityType "INSERT")
        (setq insertCounts (gj-inc (cdr (assoc 2 data)) insertCounts))
      )
      (if (and (< textCount 500) (member entityType '("TEXT" "MTEXT" "ATTRIB" "ATTDEF")))
        (progn
          (setq textValue (cdr (assoc 1 data)))
          (if (and textValue (> (strlen textValue) 0))
            (progn
              (gj-write stream (list "TEXT" layoutName layer entityType textValue))
              (setq textCount (1+ textCount))
            )
          )
        )
      )
      (setq index (1+ index))
    )
  )
  (foreach value (vl-sort typeCounts '(lambda (a b) (< (car a) (car b))))
    (gj-write stream (list "ENTITY_TYPE" (car value) (cdr value)))
  )
  (foreach value (vl-sort layerCounts '(lambda (a b) (< (car a) (car b))))
    (gj-write stream (list "ENTITY_LAYER" (car value) (cdr value)))
  )
  (foreach value (vl-sort layoutCounts '(lambda (a b) (< (car a) (car b))))
    (gj-write stream (list "ENTITY_LAYOUT" (car value) (cdr value)))
  )
  (foreach value (vl-sort insertCounts '(lambda (a b) (< (car a) (car b))))
    (gj-write stream (list "INSERT_BLOCK" (car value) (cdr value)))
  )

  (setq layerRecord (tblnext "LAYER" T))
  (while layerRecord
    (gj-write stream (list "LAYER" (cdr (assoc 2 layerRecord)) (cdr (assoc 62 layerRecord)) (cdr (assoc 6 layerRecord)) (cdr (assoc 70 layerRecord))))
    (setq layerRecord (tblnext "LAYER"))
  )
  (setq blockRecord (tblnext "BLOCK" T))
  (while blockRecord
    (gj-write stream (list "BLOCK" (cdr (assoc 2 blockRecord)) (cdr (assoc 70 blockRecord))))
    (setq blockRecord (tblnext "BLOCK"))
  )

  (gj-write stream (list "LAYOUT" "Model"))
  (close stream)
  (princ "\nGJINSPECT_COMPLETE\n")
  (princ)
)
